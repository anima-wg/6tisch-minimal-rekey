module ietf-6tisch-short-address {
  yang-version 1.1;

  namespace
    "urn:ietf:params:xml:ns:yang:ietf-6tisch-short-address";
  prefix "ietf6shortaddr";

  //import ietf-yang-types { prefix yang; }
  //import ietf-inet-types { prefix inet; }

  organization
   "IETF 6tisch Working Group";

  contact
   "WG Web:   <http://tools.ietf.org/wg/6tisch/>
    WG List:  <mailto:6tisch@ietf.org>
    Author:   Michael Richardson
              <mailto:mcr+ietf@sandelman.ca>";

  description
   "This module defines an interface to set and interrogate
    the short (16-bit) layer-2 address used in 802.15.4
    TSCH mode networks.  The short addresses are used
    in L2 frames to save space.  A lifetime is included
    in terms of TSCH Absolute Slot Number, which acts
    as a monotonically increasing clock.  ";

  revision "2017-03-01" {
    description
     "Initial version";
    reference
     "RFC XXXX: 6tisch minimal security";
  }

  // top-level container
  container ietf6shortaddresses {
    config false;
    description
      "A 16-bit short address for use by the node.";

    leaf shortaddress {
      type binary{
         length 1..2;}
      mandatory true;
      description
        "The two byte short address to be set.";
    }
    leaf validuntil {
      type uint32;
      mandatory true;
      description "The Absolute Slot Number/256 at which
                   the address ceases to be valid.";
    }

    leaf effectiveat {
      type uint32;
      description "The Absolute Slot Number/256 at which
                   time the address was originally set.
                   This is a read-only attribute that
                   records the ASN when the shortaddress
                   element was last written or updated.";
    }
  }
}
